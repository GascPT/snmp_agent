module fib_agent {

    yang-version "1";

    // namespace
    namespace "urn:srl_test/fib-agent";

    prefix "fib_agent";

    revision "2019-03-30" {
        description "Initial revision";
        reference "TBD";
    }


    grouping fib-agent-top {
        description "Top level grouping for fib_agent sample app";

        container fib-agent {
            presence "presence container";
            description "Top level enclosing container for fib_agent sample app 
                         config and operational state data";

            leaf input-fib {
                description "Route description file";
                type string;
                }
            leaf action {
                description "add or delete or replace";
                type string;
                }
            list fib-result {
                key name;
                config false;

            leaf name {
                 type string;
                }
            leaf programed-state {
                type boolean;
                description "Programmed state of fib routes";
                }
            leaf reason-code {
                type string;
                description "Reason for unprogrammed fib";
                }
            }
            leaf route-count{
                type uint64;
                config false;
            }
            leaf programmed-routes{
                type uint64;
                config false;
            }
        }
    }

    // data definition statements
    uses fib-agent-top;
}
